; File: DEBUG.LSP  (C)		05/29/87	Soft Warehouse, Inc.


(IF (EQ *INIT-WINDOW* '*INIT-WINDOW*) (SETQ *INIT-WINDOW* "Debug"))
(SETQ *WINDOW-TYPES* (SORT (ADJOIN "Debug" *WINDOW-TYPES*) 'STRING<))
(SETQ DRIVER 'WINDOWS)

(SETQ *HISTORY-LENGTH* 25)
(SETQ *DEFAULT-TYPE* 'LSP)
(SETQ *SHOW-LOAD* T)
(IF (ATOM *DEBUG-FUNCTIONS*)
    (SETQ *DEBUG-FUNCTIONS* NIL) )

(DEFUN "Debug" (COMMAND
	FUNCTION BREAK *TRACE-HISTORY* *DEBUG-MODE* *BACKTRACE* *DEBUG-ROW*
    *FILE-NAME* *LOCAL-DEMONS* *INPUT-FILE* *OUTPUT-FILE*)
  ((EQ COMMAND 'CREATE-WINDOW)
    (LIST "Debug" NIL NIL NIL "Continuous" NIL 0) )
  ((EQ COMMAND 'CLOSE-WINDOW)
    (UNTRACE-ALL)
    0 )
  (SETQ *FILE-NAME* "")
  (UNWIND-PROTECT
    (PROGN
      ((EQ COMMAND 'UPDATE-WINDOW)
	(CURRENT-WINDOW)
	(CLEAR-SCREEN)
	(SETQ *DEBUG-ROW* (ROW)) )
      ((EQ COMMAND 'DISPLAY)
	(SHOW-PROMPT "Press ESC to abort")
	(CURRENT-DEBUG-WINDOW)
	(TERPRI)
	(CURSOR-ON)
	((LAMBDA (*AUTO-NEWLINE* *INTERRUPT-HOOK*)
	   (CATCH NIL (PRIN1 (EVAL BREAK)))) T 'CONSOLE-BREAK)
	(CURSOR-OFF)
	(SETQ *DEBUG-ROW* (ROW)) )
      ((OR (EQ COMMAND 'TRACEIN) (EQ COMMAND 'TRACEOUT))
	( ((EQ *DEBUG-MODE* "Off"))
	  (CURRENT-DEBUG-WINDOW)
	  (DISPLAY-TRACE (CAR *TRACE-HISTORY*))
	  (SETQ *DEBUG-ROW* (ROW))
	  ((EQ *DEBUG-MODE* "Continuous"))
	  ((EQ COMMAND 'TRACEOUT))
	  ((LAMBDA (*GLOBAL-DEMONS*) (CATCH 'RESUME-PROGRAM
	      (LOOP
		(EXECUTE-OPTION 'COMMAND *BREAK-OPTIONS*) ) ) )
	    '((22 . TOGGLE-INSERT))) )
	BREAK )
      (CLEAR-STATUS "Debug")
      (FREE-STATUS)
      (LOOP
	(EXECUTE-OPTION 'COMMAND *DEBUG-OPTIONS*) ) )
    (UPDATE-STATE '(FUNCTION BREAK *TRACE-HISTORY*
			*DEBUG-MODE* *BACKTRACE* *DEBUG-ROW*)) ) )

(SETQ *DEBUG-OPTIONS* '(
	("Author" . LISP-EVAL)
	("Debug" DEBUG (
		("Mode" . DEBUG-MODE)
		("Trace" . TRACE-FUNCTIONS)
		("Untrace" "DEBUG UNTRACE" (
			("All" . UNTRACE-ALL)
			("Some" . UNTRACE-FUNCTIONS) )) ))
	("History" . TRACE-HISTORY)
	("Mode" . SET-INSERT)
	("Options" OPTIONS (
		("Color" . SET-COLOR)
		("Display" . SET-DISPLAY)
		("Execute" . GO-DOS)
		("Mute" . SET-MUTE) ))
	("Print" . PRINT-TEXT-FILE)
	("Quit" . QUIT-PROGRAM)
	("Transfer" TRANSFER (
		("Delete" . DELETE-TEXT-FILE)
		("Load" . LOAD-SOURCE-FILE)
		("Save" . SAVE-SYS-FILE) ))
	("Window" . CHANGE-WINDOW) ))

(SETQ *BREAK-OPTIONS* (DELETE-IF '(LAMBDA (OPTION)
				    (MEMBER (CAR OPTION) '("Quit" "Window")))
				 (COPY-LIST *DEBUG-OPTIONS*)))
(SETQ *BREAK-OPTIONS*
	(MERGE '(("Backtrace" . BACKTRACE) ("Resume" . RESUME-PROGRAM))
		*BREAK-OPTIONS*
		'(LAMBDA (OPT1 OPT2) (STRING< (CAR OPT1) (CAR OPT2))) ))


(IF (NOT (GETD 'PRINT-TEXT-FILE T))
    (MOVD 'NULL 'PRINT-TEXT-FILE) )

(IF (NOT (GETD 'DELETE-TEXT-FILE T))
    (MOVD 'NULL 'DELETE-TEXT-FILE) )

(DEFUN LOAD-SOURCE-FILE (
    FILE-NAME EXPN)
  (LOOP
    (SETQ FILE-NAME (PROMPT-TEXT-FILE "TRANSFER LOAD source file: " ""))
    ((EQ FILE-NAME "") NIL)
    (SHOW-PROMPT "Press ESC to abort")
    (CURRENT-DEBUG-WINDOW)
    (TERPRI)
    (CURSOR-ON)
    (SETQ EXPN ((LAMBDA (*AUTO-NEWLINE* *INTERRUPT-HOOK*)
		  (CATCH NIL (LOAD FILE-NAME *SHOW-LOAD*))) T 'CONSOLE-BREAK))
    (CURSOR-OFF)
    (SETQ *DEBUG-ROW* (ROW))
    (FREE-STATUS)
    ((IDENTITY EXPN))
    (ERROR-BEEP) ) )

(DEFUN SAVE-SYS-FILE (
    FILE-NAME)
  (LOOP
    (SETQ FILE-NAME (PROMPT-TEXT-FILE "TRANSFER SAVE SYS file: " ""))
    ((EQ FILE-NAME "") NIL)
    ((SAVE FILE-NAME))
    (ERROR-BEEP) ) )

(DEFUN LISP-EVAL (
    STRING *PRINTER-ECHO*)
  (LOOP
    (SETQ STRING (PROMPT-INPUT "Enter form for evaluation" "AUTHOR form: " ""))
    ((EQ *LINE-TERMINATOR* 27) NIL)
    ((EQ STRING "") NIL)
    (SETQ *OPTIONS*)
    (SHOW-PROMPT "Press ESC to abort")
    (CURRENT-DEBUG-WINDOW)
    (TERPRI NIL T)
    (CURSOR-ON)
    ((LAMBDA (*AUTO-NEWLINE* *INTERRUPT-HOOK*)
	(CATCH NIL (READ-STRING-EVAL STRING))) T 'CONSOLE-BREAK)
    (CURSOR-OFF)
    (SETQ *DEBUG-ROW* (ROW))
    (FREE-STATUS)
    (SETQ *TRACE-HISTORY* (FOURTH (WINDOW-STATE))) ) )

(DEFUN READ-STRING-EVAL (STRING)
  (TERPRI NIL T)
  (WRITE-STRING "$ " T)
  (WRITE-LINE STRING T)
  (SETQ - (READ-FROM-STRING (PACK* STRING "]")))
  (PSETQ * (UNWIND-PROTECT (EVAL -) (SETQ +++ ++  ++ +	+ -))
	 *** **
	 ** *)
  (WRITE * T) )

(DEFUN RESUME-PROGRAM ()
  (THROW 'RESUME-PROGRAM) )


(DEFUN TRACE-FUNCTIONS (
    FUNCTION NAME BODY LST)
  (LOOP
    (SETQ FUNCTION (STRING-UPCASE (PROMPT-INPUT "Enter function name"
					"DEBUG TRACE function: " "")))
    ((EQ *LINE-TERMINATOR* 27) NIL)
    ((EQ FUNCTION "")
      (MAPC 'TRACE-FUNCTION LST) )
    ( ((OR (EQ (GETD FUNCTION T) 'LAMBDA)
	   (MEMBER FUNCTION *SPECIAL-FORMS*))
	((CONSP (GETD FUNCTION))
	  ((AND (NOT (MEMBER FUNCTION LST))
		(NOT (MEMBER FUNCTION *DEBUG-FUNCTIONS*)))
	    (PUSH FUNCTION LST) )
	  (ERROR-BEEP) )
	((AND (NOT (MEMBER FUNCTION *SPECIAL-FORMS*))
	      (SETQ BODY (GETD (PACK* FUNCTION "!D")))
	      (NEQ (SECOND (FIFTH (THIRD BODY))) (WINDOW-STATE)))
	  (ERROR-BEEP) )
	(LOOP
	  (SETQ NAME (STRING-UPCASE (PROMPT-INPUT "Enter function name"
			   (PACK* "Trace " FUNCTION " in function: ") "")))
	  ((EQ *LINE-TERMINATOR* 27)
	    (RETURN) )
	  ((EQ NAME ""))
	  ( ((AND (EQ (GETD NAME T) 'LAMBDA)
		  (CONSP (GETD NAME))
		  (NOT (MEMBER (CONS FUNCTION NAME) LST 'EQUAL))
		  (NOT (MEMBER (CONS FUNCTION NAME) *DEBUG-FUNCTIONS* 'EQUAL)))
	      (PUSH (CONS FUNCTION NAME) LST) )
	    (ERROR-BEEP) ) ) )
      (ERROR-BEEP) ) ) )

(DEFUN TRACE-FUNCTION (FUNCTION
    NAME BODY)
  (PUSH FUNCTION *DEBUG-FUNCTIONS*)
  ( ((ATOM FUNCTION)
      (SETQ NAME FUNCTION) )
    (PUTD (CDR FUNCTION) (SUBST (PACK* (CAR FUNCTION) "!D")
				(CAR FUNCTION)
				(GETD (CDR FUNCTION))))
    (SETQ NAME (CAR FUNCTION)
	  FUNCTION (PACK* NAME "!D"))
    ((MEMBER NAME *SPECIAL-FORMS*))
    (PUTD FUNCTION (LIST 'LAMBDA 'LST
			 (LIST 'APPLY (LIST 'QUOTE NAME) 'LST))) )
  (SETQ BODY (GETD FUNCTION))
  (PUTD FUNCTION (LIST (FIRST BODY)
		       (SECOND BODY)
		       (LIST 'DEBUG-WINDOW
			      '(QUOTE TRACEIN)
			      (LIST 'QUOTE NAME)
			      (IF (ATOM (SECOND BODY))
				  (SECOND BODY)
				  (CONS 'LIST (SECOND BODY)))
			      (LIST 'QUOTE (WINDOW-STATE)))
		       (LIST 'DEBUG-WINDOW
			     '(QUOTE TRACEOUT)
			     (LIST 'QUOTE NAME)
			     (CONS 'PROGN (CDDR BODY))
			     (LIST 'QUOTE (WINDOW-STATE))))) )


(DEFUN UNTRACE-FUNCTIONS (
    FUNCTION NAME BODY LST)
  (LOOP
    (SETQ FUNCTION (STRING-UPCASE (PROMPT-INPUT "Enter function name"
					"DEBUG UNTRACE function: " "")))
    ((EQ *LINE-TERMINATOR* 27) NIL)
    ((EQ FUNCTION "")
      (MAPC 'UNTRACE-FUNCTION LST) )
    ( ((OR (EQ (GETD FUNCTION T) 'LAMBDA)
	   (MEMBER FUNCTION *SPECIAL-FORMS*))
	((CONSP (GETD FUNCTION))
	  ((AND (NOT (MEMBER FUNCTION LST))
		(MEMBER FUNCTION *DEBUG-FUNCTIONS*)
		(SETQ BODY (GETD FUNCTION))
		(EQ (SECOND (FIFTH (THIRD BODY))) (WINDOW-STATE)))
	    (PUSH FUNCTION LST) )
	  (ERROR-BEEP) )
	((OR (AND (NOT (MEMBER FUNCTION *SPECIAL-FORMS*))
		  (SETQ BODY (GETD (PACK* FUNCTION "!D")))
		  (NEQ (SECOND (FIFTH (THIRD BODY))) (WINDOW-STATE)))
	     (NOT (ASSOC FUNCTION *DEBUG-FUNCTIONS*)))
	  (ERROR-BEEP) )
	(LOOP
	  (SETQ NAME (STRING-UPCASE (PROMPT-INPUT "Enter function name"
			   (PACK* "Untrace " FUNCTION " in function: ") "")))
	  ((EQ *LINE-TERMINATOR* 27)
	    (RETURN) )
	  ((EQ NAME ""))
	  ( ((AND (NOT (MEMBER (CONS FUNCTION NAME) LST 'EQUAL))
		  (MEMBER (CONS FUNCTION NAME) *DEBUG-FUNCTIONS* 'EQUAL))
	      (PUSH (CONS FUNCTION NAME) LST) )
	    (ERROR-BEEP) ) ) )
      (ERROR-BEEP) ) ) )

(DEFUN UNTRACE-ALL ()
  (LOOP
    ((NOTANY 'UNTRACE-FUNCTION *DEBUG-FUNCTIONS*)) ) )

(DEFUN UNTRACE-FUNCTION (FUNCTION
    NAME BODY)
  ((ATOM FUNCTION)
    (SETQ BODY (GETD FUNCTION))
    ((EQ (SECOND (FIFTH (THIRD BODY))) (WINDOW-STATE))
      (SETQ *DEBUG-FUNCTIONS* (DELETE FUNCTION *DEBUG-FUNCTIONS* 'EQUAL))
      (PUTD FUNCTION (LIST* 'LAMBDA (SECOND BODY)
			    (CDR (FOURTH (FOURTH BODY))))) ) )
  (SETQ BODY (GETD (PACK* (CAR FUNCTION) "!D")))
  ((EQ (SECOND (FIFTH (THIRD BODY))) (WINDOW-STATE))
    (SETQ *DEBUG-FUNCTIONS* (DELETE FUNCTION *DEBUG-FUNCTIONS* 'EQUAL))
    (PUTD (CDR FUNCTION) (SUBST (CAR FUNCTION)
				(PACK* (CAR FUNCTION) "!D")
				(GETD (CDR FUNCTION))))
    ((ASSOC (CAR FUNCTION) *DEBUG-FUNCTIONS*))
    ((MEMBER (CAR FUNCTION) *SPECIAL-FORMS*))
    (REMD (PACK* (CAR FUNCTION) "!D")) ) )


(SETQ *SPECIAL-FORMS* '(SETQ INCQ DECQ))

(PUTD 'SETQ!D '(NLAMBDA LST!D
  (LOOP
    ((NULL (CDDR LST!D))
      (SET (POP LST!D) (EVAL (POP LST!D))) )
    (SET (POP LST!D) (EVAL (POP LST!D))) ) ))

(PUTD 'INCQ!D '(NLAMBDA LST!D
  (SET (CAR LST!D)
       (+ (EVAL (CAR LST!D)) (IF (CDR LST!D) (EVAL (CADR LST!D)) 1))) ))

(PUTD 'DECQ!D '(NLAMBDA LST!D
  (SET (CAR LST!D)
       (- (EVAL (CAR LST!D)) (IF (CDR LST!D) (EVAL (CADR LST!D)) 1))) ))


(DEFUN DEBUG-WINDOW (COMMAND FUNCTION BREAK STATE
    WINDOW PANE ROW COL FOREGROUND-COLOR BACKGROUND-COLOR *INTERRUPT-HOOK*)
  (SETQ WINDOW (POSITION-IF '(LAMBDA (WINDOW)
			       (SETQ PANE (POSITION STATE (SECOND WINDOW))) )
			    *WINDOWS*))
  ( ((EQ COMMAND 'TRACEOUT)			;(POP *BACKTRACE*)
      (REPLACE-NTH (CDR (NTH 5 STATE)) STATE 5) ) )
  (REPLACE-NTH					;(PUSH TRACE *TRACE-HISTORY*)
     (CONS (LIST FUNCTION BREAK COMMAND (LENGTH (NTH 5 STATE))) (NTH 3 STATE))
     STATE 3)
  (DELETE-NTH (NTH 3 STATE) *HISTORY-LENGTH*)
  ( ((EQ COMMAND 'TRACEIN)			;(PUSH TRACE *BACKTRACE*)
      (REPLACE-NTH (CONS (LIST FUNCTION BREAK) (NTH 5 STATE)) STATE 5) ) )
  ((NEQ PANE (WINDOW-PANE WINDOW)) BREAK)
  (SETQ ROW (ROW)
	COL (COLUMN)
	FOREGROUND-COLOR (FOREGROUND-COLOR)
	BACKGROUND-COLOR (BACKGROUND-COLOR))
  (SETQ BREAK ((LAMBDA (*CURRENT-WINDOW*)
		  (APPLY "Debug" COMMAND FUNCTION BREAK (NTHCDR 3 STATE)) )
		WINDOW))
  (CURRENT-WINDOW)
  (FOREGROUND-COLOR FOREGROUND-COLOR)
  (BACKGROUND-COLOR BACKGROUND-COLOR)
  (SET-CURSOR ROW COL)
  BREAK )

(DEFUN TRACE-HISTORY ()
  ((NULL *TRACE-HISTORY*))
  (CURRENT-DEBUG-WINDOW)
  (TERPRI)
  (MAPC 'DISPLAY-TRACE (REVERSE *TRACE-HISTORY*))
  (SETQ *DEBUG-ROW* (ROW)) )

(DEFUN DISPLAY-TRACE (TRACE
    *AUTO-NEWLINE*)
  (SETQ *AUTO-NEWLINE* T)
  (TERPRI)
  (SPACES (* (FOURTH TRACE) 2))
  (PRINC (FIRST TRACE))
  (WRITE-STRING " ")
  (IF (EQ (THIRD TRACE) 'TRACEOUT) (WRITE-STRING "= "))
  (PRIN1 (SECOND TRACE))
  ((EQ (READ-CONSOLE-STATUS) 19)
    (LOOP
      ((READ-CONSOLE-STATUS)) ) ) )

(DEFUN BACKTRACE (
    *AUTO-NEWLINE*)
  ((NULL *BACKTRACE*))
  (CURRENT-DEBUG-WINDOW)
  (TERPRI)
  (SETQ *AUTO-NEWLINE* T)
  (MAPC '(LAMBDA (FORM)
	   (TERPRI)
	   (PRINC (CAR FORM))
	   (WRITE-STRING " ")
	   (PRIN1 (CADR FORM)) )
	*BACKTRACE*)
  (SETQ *DEBUG-ROW* (ROW)) )

(DEFUN DEBUG-MODE ()
  (RPLACA (CAR DEBUG-MODE) *DEBUG-MODE*)
  ((MODE-QUERY 'DEBUG DEBUG-MODE)
    (REPLACE-NTH (SETQ *DEBUG-MODE* (CAAR DEBUG-MODE)) (WINDOW-STATE) 4) ) )

(SETQ DEBUG-MODE '(
  ("Continuous" 0 0 "Select debug mode" "Mode" ("Continuous" "Step" "Off"))))

(DEFUN CURRENT-DEBUG-WINDOW ()
  (CURRENT-WINDOW)
  (SET-CURSOR *DEBUG-ROW* 0) )

(OR (GETD 'WINDOWS T)
    (LOAD "WINDOWS.LSP")
    (SOME '(LAMBDA (FILE)
	     (SETQ FILE (NREVERSE (UNPACK FILE)))
	     (LOAD (PACK (NREVERSE (OR (MEMBER '\\ FILE) (MEMBER ': FILE))
				   (LIST "WINDOWS.LSP")))) )
	  (INPUT-FILES) )
    (TERPRI NIL T)
    (WRITE-LINE "Cannot find WINDOWS.LSP" T) )
